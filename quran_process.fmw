FME workspace quran_process.fmw

Parameters:
- SourceDataset_SPATIALITE = $(FME_MF_DIR)q_nlp.db   # SpatiaLite Database
- DestDataset_SPATIALITE = $(FME_MF_DIR)q_nlp.db   # SpatiaLite Database
- DestDataset_SPATIALITE_6 = $(FME_MF_DIR)q_nlp.db   # SpatiaLite Database
- SourceDataset_CSV2_3 = $(FME_MF_DIR)arabic-original.csv   # Source CSV (Comma Separated Value) File(s)
- DestDataset_SPATIALITE_5 = $(FME_MF_DIR)q_nlp.db   # SpatiaLite Database

Readers:
- SPATIALITE_1: SPATIALITE from $(SourceDataset_SPATIALITE)
- CSV2_2: CSV2 from $(SourceDataset_CSV2_3)

Writers:
- SPATIALITE_2: SPATIALITE to $(DestDataset_SPATIALITE)
- SPATIALITE_3: SPATIALITE to $(DestDataset_SPATIALITE_6)
- SPATIALITE_4: SPATIALITE to $(DestDataset_SPATIALITE_5)

q_content (reader SPATIALITE_1)
    attributes: juz integer, ayat integer, surah string(255), surah_desc string(255)
    -> Aggregator
    -> FeatureJoiner_2 [LEFT]
Aggregator
    ACCUM_ATTRS_NAME = Use Attributes From One Feature
    AGGREGATE_TYPE = Homogeneous Collection (If Possible)
    CONCAT_ATTRS = ayat surah_desc
    COUNT_ATTR = TOTAL
    GROUP_BY = surah
    MODE = Geometry - Assemble One Level
    SEP = ,
    AGGREGATE -> AttributeManager
AttributeManager
    -> RClusterCalculator [Data]
RClusterCalculator
    algorithm = "Lloyd"
    attribute1 = TOTAL
    centers = 3
    iter.max = 10
    nstart = 1
    -> Sorter
Sorter
    SORT_PARM = cluster NUMERIC ASCENDING TOTAL NUMERIC ASCENDING
    SORTED -> FeatureJoiner [LEFT]
CSV (reader CSV2_2)
    attributes: surah string, ayah string, verse string
    -> Aggregator_2
    -> FeatureJoiner_2 [RIGHT]
FeatureJoiner_2
    ATTR_CONFLICT_RES = Use Left
    GEOMETRY_HANDLING = Use Left
    JOIN_KEYS = juz surah AUTO ayat ayah AUTO
    JOIN_MODE = Inner
    JOINED -> q_content_translate (writer SPATIALITE_4)
q_content_translate (writer SPATIALITE_4)
    attributes: juz integer, ayat integer, surah string(255), surah_desc string(255), surah_arabic string(500)
Aggregator_2
    ACCUM_ATTRS_NAME = Use Attributes From One Feature
    AGGREGATE_TYPE = Homogeneous Collection (If Possible)
    CONCAT_ATTRS = verse
    COUNT_ATTR = TOTAL
    GROUP_BY = surah
    MODE = Geometry - Assemble One Level
    SEP = ,
    AGGREGATE -> Sorter_2
Sorter_2
    SORT_PARM = surah NUMERIC ASCENDING
    SORTED -> FeatureJoiner [RIGHT]
FeatureJoiner
    ATTR_CONFLICT_RES = Use Left
    GEOMETRY_HANDLING = Use Left
    JOIN_KEYS = juz surah AUTO
    JOIN_MODE = Inner
    JOINED -> q_juz_summary (writer SPATIALITE_3)
q_juz_summary (writer SPATIALITE_3)
    attributes: surah string(255), surah_desc string(10000), juz integer, total integer, cluster integer, arabic_surah string(10000)
q_juz (reader SPATIALITE_1)
    attributes: Juz integer, Nama.Surah string(255), Maksud string(255)
    -> q_juz
q_juz: Inspector
q_surah (reader SPATIALITE_1)
    attributes: Surah integer, Nama_Surah string(255), Ayat integer, Maksud string(255)
    -> q_surah
q_surah: Inspector

FME custom transformer RClusterCalculator
A Cluster Analysis finds groups in data using R. The RClusterCalculator can accept up to ten numerical attributes and can perform three different cluster algorithms. 
Requirements
R Installed - How to install R Instructions
sqldf R package installed
FME 2018.0+
Input Ports
This transformer accepts any floating point feature. 
Output Ports
Outputs the attributes that were tested as well as the number of clusters associated with each attribute. 
Parameters
$(attribute1)  (Mandatory) - this transformer requires at least one numerical attribute to work 
$(attribute2) to - $(attribute10) (Optional) - Additional attributes to perform the calcuation with, these are optional
$(centers) - Number of clusters to calculate
$(iter.max) - Maximum number of iterations over the data
$(nstart) - Number of random sets should be chosen 
$(algorithm) - Which algorithm should be used; Hartigan-Wong, Lloyd / Forgy, or MacQueen. 
Resources
Cluster Package R Documentation
RCaller: Ins and outs of using R in FME
Basic Statistical Custom Transformers
Other Statistical Transformers
ROneSampleTTestCalculator  
RTwoSampleTTestCalculator  
PyShapiroWilksCalculator
RShapiroWilksCalculator

Parameters:
- GROUP_BY =   # "" Group By
- attribute2 =   # " " Select 2nd attribute to include in analysis (optional)
- attribute3 =   # " " Select 3rd attribute to include in analysis (optional)
- attribute4 =   # " " Select 4th attribute to include in analysis (optional)
- attribute5 =   # " " Select 5th attribute to include in analysis (optional)
- attribute6 =   # " " Select 6th attribute to include in analysis (optional)
- attribute7 =   # " " Select 7th attribute to include in analysis (optional)
- attribute8 =   # " " Select 8th attribute to include in analysis (optional)
- attribute9 =   # " " Select 9th attribute to include in analysis (optional)
- attribute10 =   # " " Select 10th attribute to include in analysis (optional)
- centers =   # How many clusters would you like to calculate?
- iter.max = 10   # What is the maximum number of iterations allowed?
- nstart = 1   # How many random sets should be chosen?
- algorithm = "Hartigan-Wong"   # / Forgy,"Lloyd"%MacQueen,"MacQueen" Which algorithm do you want to use?
- attribute1 =   # " " Select 1st attribute to include in analysis (mandatory)

Data (input)
    -> Tester_centers
Tester_centers
    BOOL_OP = AND
    TEST_CLAUSE = TEST $(centers) TYPE NUM
    TEST_MODE = TEST
    PASSED -> Tester_iter.max
    FAILED -> AttributeCreator_centers
Tester_iter.max
    BOOL_OP = AND
    TEST_CLAUSE = TEST $(iter.max) TYPE NUM
    TEST_MODE = TEST
    PASSED -> Tester_nstart
    FAILED -> AttributeCreator_iter.max
Tester_nstart
    BOOL_OP = AND
    TEST_CLAUSE = TEST $(nstart) TYPE NUM
    TEST_MODE = TEST
    PASSED -> Tester_algorithm
    FAILED -> AttributeCreator_nstart
Note: To add addiitonal attributes for analysis: / 1. Duplicate attribute10 Published Parameter and change 10 to 11 (or 12, 13, etc.) throughout. / 2. Duplicate TestFilter10, replace $(attribute10) with $(attribute11) etc. / 3. Duplicate AttributeCreator_10, replace $(attribute10) with $(attribute11) etc. / 4. Add $(attribute11) etc. to the AttributeManager. / 4. In the RCaller, add attribute11 etc. under Table > Columns. / 5. Add $(attribute11) etc. to all three AttributeRenamers.
Tester_algorithm
    BOOL_OP = AND
    TEST_CLAUSE = TEST $(algorithm) TYPE STRING
    TEST_MODE = TEST
    PASSED -> Tester_1
    FAILED -> AttributeCreator_algorithm
Tester_1
    BOOL_OP = AND
    TEST_CLAUSE = TEST @Value($(attribute1)) TYPE NUM
    TEST_MODE = TEST
    PASSED -> TestFilter_2
    FAILED -> AttributeCreator_1
TestFilter_2
    DEFAULT_VALUE = <UNFILTERED>
    TEST_LIST:
      "BOOL_OP,OR,COMPOSITE_TEST,""""""<Unused>"""""",TEST_CLAUSE,TEST @Value($(attribute2)) TYPE NUM
      TEST $(attribute2) NOT_ATTRIBUTE_HAS_A_VALUE """,Passed,"BOOL_OP,OR,COMPOSITE_TEST,""""""<Unused>"""""",TEST_CLAUSE,TEST @Value($(attribute2)) ATTRIBUTE_HAS_A_VALUE """,Failed
    Passed -> TestFilter_3
    Failed -> AttributeCreator_2
TestFilter_3
    DEFAULT_VALUE = <UNFILTERED>
    TEST_LIST:
      "BOOL_OP,OR,COMPOSITE_TEST,""""""<Unused>"""""",TEST_CLAUSE,TEST @Value($(attribute3)) TYPE NUM
      TEST $(attribute3) NOT_ATTRIBUTE_HAS_A_VALUE """,Passed,"BOOL_OP,OR,COMPOSITE_TEST,""""""<Unused>"""""",TEST_CLAUSE,TEST @Value($(attribute3)) ATTRIBUTE_HAS_A_VALUE """,Failed
    Passed -> TestFilter_4
    Failed -> AttributeCreator_3
TestFilter_4
    DEFAULT_VALUE = <UNFILTERED>
    TEST_LIST:
      "BOOL_OP,OR,COMPOSITE_TEST,""""""<Unused>"""""",TEST_CLAUSE,TEST @Value($(attribute4)) TYPE NUM
      TEST $(attribute4) NOT_ATTRIBUTE_HAS_A_VALUE """,Passed,"BOOL_OP,OR,COMPOSITE_TEST,""""""<Unused>"""""",TEST_CLAUSE,TEST @Value($(attribute4)) ATTRIBUTE_HAS_A_VALUE """,Failed
    Passed -> TestFilter_5
    Failed -> AttributeCreator_4
TestFilter_5
    DEFAULT_VALUE = <UNFILTERED>
    TEST_LIST:
      "BOOL_OP,OR,COMPOSITE_TEST,""""""<Unused>"""""",TEST_CLAUSE,TEST @Value($(attribute5)) TYPE NUM
      TEST $(attribute5) NOT_ATTRIBUTE_HAS_A_VALUE """,Passed,"BOOL_OP,OR,COMPOSITE_TEST,""""""<Unused>"""""",TEST_CLAUSE,TEST @Value($(attribute5)) ATTRIBUTE_HAS_A_VALUE """,Failed
    Passed -> TestFilter_6
    Failed -> AttributeCreator_5
TestFilter_6
    DEFAULT_VALUE = <UNFILTERED>
    TEST_LIST:
      "BOOL_OP,OR,COMPOSITE_TEST,""""""<Unused>"""""",TEST_CLAUSE,TEST @Value($(attribute6)) TYPE NUM
      TEST $(attribute6) NOT_ATTRIBUTE_HAS_A_VALUE """,Passed,"BOOL_OP,OR,COMPOSITE_TEST,""""""<Unused>"""""",TEST_CLAUSE,TEST @Value($(attribute6)) ATTRIBUTE_HAS_A_VALUE """,Failed
    Passed -> TestFilter_7
    Failed -> AttributeCreator_6
TestFilter_7
    DEFAULT_VALUE = <UNFILTERED>
    TEST_LIST:
      "BOOL_OP,OR,COMPOSITE_TEST,""""""<Unused>"""""",TEST_CLAUSE,TEST @Value($(attribute7)) TYPE NUM
      TEST $(attribute7) NOT_ATTRIBUTE_HAS_A_VALUE """,Passed,"BOOL_OP,OR,COMPOSITE_TEST,""""""<Unused>"""""",TEST_CLAUSE,TEST @Value($(attribute7)) ATTRIBUTE_HAS_A_VALUE """,Failed
    Passed -> TestFilter_8
    Failed -> AttributeCreator_7
TestFilter_8
    DEFAULT_VALUE = <UNFILTERED>
    TEST_LIST:
      "BOOL_OP,OR,COMPOSITE_TEST,""""""<Unused>"""""",TEST_CLAUSE,TEST @Value($(attribute8)) TYPE NUM
      TEST $(attribute8) NOT_ATTRIBUTE_HAS_A_VALUE """,Passed,"BOOL_OP,OR,COMPOSITE_TEST,""""""<Unused>"""""",TEST_CLAUSE,TEST @Value($(attribute8)) ATTRIBUTE_HAS_A_VALUE """,Failed
    Passed -> TestFilter_9
    Failed -> AttributeCreator_8
TestFilter_9
    DEFAULT_VALUE = <UNFILTERED>
    TEST_LIST:
      "BOOL_OP,OR,COMPOSITE_TEST,""""""<Unused>"""""",TEST_CLAUSE,TEST @Value($(attribute9)) TYPE NUM
      TEST $(attribute9) NOT_ATTRIBUTE_HAS_A_VALUE """,Passed,"BOOL_OP,OR,COMPOSITE_TEST,""""""<Unused>"""""",TEST_CLAUSE,TEST @Value($(attribute9)) ATTRIBUTE_HAS_A_VALUE """,Failed
    Passed -> TestFilter_10
    Failed -> AttributeCreator_9
TestFilter_10
    DEFAULT_VALUE = <UNFILTERED>
    TEST_LIST:
      "BOOL_OP,OR,COMPOSITE_TEST,""""""<Unused>"""""",TEST_CLAUSE,TEST @Value($(attribute10)) TYPE NUM
      TEST $(attribute10) NOT_ATTRIBUTE_HAS_A_VALUE """,Passed,"BOOL_OP,OR,COMPOSITE_TEST,""""""<Unused>"""""",TEST_CLAUSE,TEST @Value($(attribute10)) ATTRIBUTE_HAS_A_VALUE """,Failed
    Passed -> UUIDGenerator
    Failed -> AttributeCreator_10
Note: Generate UUID so featuers can be analyzed in RCaller and then joined back together
UUIDGenerator
    UUID_ATTR = id
    -> AttributeManager
    -> FeatureJoiner [LEFT]
Note: Coerce attributes to a real64 and rename
AttributeManager
    ATTR_TABLE:
      SET_TO $(attribute1) > attribute1 = @real64(@Value($(attribute1)))
      SET_TO $(attribute2) > attribute2 = @real64(@Value($(attribute2)))
      SET_TO $(attribute3) > attribute3 = @real64(@Value($(attribute3)))
      SET_TO $(attribute4) > attribute4 = @real64(@Value($(attribute4)))
      SET_TO $(attribute5) > attribute5 = @real64(@Value($(attribute5)))
      SET_TO $(attribute6) > attribute6 = @real64(@Value($(attribute6)))
      SET_TO $(attribute7) > attribute7 = @real64(@Value($(attribute7)))
      SET_TO $(attribute8) > attribute8 = @real64(@Value($(attribute8)))
      SET_TO $(attribute9) > attribute9 = @real64(@Value($(attribute9)))
      SET_TO $(attribute10) > attribute10 = @real64(@Value($(attribute10)))
      SET_TO centers = $(centers)
      SET_TO iter.max = $(iter.max)
      SET_TO nstart = $(nstart)
      SET_TO algorithm = $(algorithm)
    -> RCaller [R]
Note: Join R results back to features
FeatureJoiner
    ATTR_CONFLICT_RES = Use Left
    GEOMETRY_HANDLING = Use Left
    JOIN_KEYS = id id AUTO
    JOIN_MODE = Left
    JOINED -> AttributeExposer_2
Note: Expose user parameter attributes
AttributeExposer_2
    ATTR_LIST = attribute1,attribute2,attribute3,attribute4,attribute5,attribute6,attribute7,attribute8,attribute9,attribute10
    -> AttributeExposer_4
    -> FeatureJoiner_2 [LEFT]
    -> StatisticsCalculator
Output (output)
Cluster_Means (output)
Complete (output)
Junction
    -> AttributeExposer_6
<REJECTED> (output)

Bookmark: RCaller - calculate clusters
RCaller
    OUTPUT_SCHEMA = id cluster
    QUERY_DEF:
      Output,process <- function(cluster) {
        # Prepare data
        drops <- c("id","centers","iter.max","nstart","algorithm") # id as column to drop
        # Function to cluster data
        cluster_fun <- function(x) {
          centers <- x$centers[1]
          iter.max <- x$iter.max[1]
          nstart <- x$nstart[1]
          algorithm <- gsub("\"","",as.character(R$algorithm[1]),fixed=T)
          x <- x[ , !(names(x) %in% drops)] # remove id column
          kmeans(as.data.frame(na.omit(scale(x[, colSums(is.na(x)) == 0]))), centers = centers, iter.max = iter.max, nstart = nstart, algorithm = algorithm)
        }
        fit <- by(R, as.factor(R$centers), cluster_fun)
        # Append cluster assignment to data.frame for output
        cluster_list <- lapply(fit, '[[', 1)
        R$cluster <- unname(unlist(cluster_list))

        return(data.frame(R))
      }

      handle_error <- function(c) {
        error <- data.frame(c("R_SCRIPT_EXECUTION_ERROR"), c(conditionMessage(c)))
        colnames(error) <- c("fme_rejection_code", "fme_rejection_message")
        return(error)
      }

      fmeOutput <- tryCatch(process(cluster), error = handle_error),id cluster
    R_SCRIPT:
      process <- function(cluster) {
        # Prepare data
        drops <- c("id","centers","iter.max","nstart","algorithm") # id as column to drop
        # Function to cluster data
        cluster_fun <- function(x) {
          centers <- x$centers[1]
          iter.max <- x$iter.max[1]
          nstart <- x$nstart[1]
          algorithm <- gsub("\"","",as.character(R$algorithm[1]),fixed=T)
          x <- x[ , !(names(x) %in% drops)] # remove id column
          kmeans(as.data.frame(na.omit(scale(x[, colSums(is.na(x)) == 0]))), centers = centers, iter.max = iter.max, nstart = nstart, algorithm = algorithm)
        }
        fit <- by(R, as.factor(R$centers), cluster_fun)
        # Append cluster assignment to data.frame for output
        cluster_list <- lapply(fit, '[[', 1)
        R$cluster <- unname(unlist(cluster_list))

        return(data.frame(R))
      }

      handle_error <- function(c) {
        error <- data.frame(c("R_SCRIPT_EXECUTION_ERROR"), c(conditionMessage(c)))
        colnames(error) <- c("fme_rejection_code", "fme_rejection_message")
        return(error)
      }

      fmeOutput <- tryCatch(process(cluster), error = handle_error)
    TABLE_DEF = R,id,varchar(36),attribute1,float,attribute2,float,attribute3,float,attribute4,float,attribute5,float,attribute6,float,attribute7,float,attribute8,float,attribute9,float,attribute10,float,centers,integer,iter.max,integer,nstart,integer,algorithm,text
    -> FeatureJoiner [RIGHT]

Bookmark: Manage rejection codes and messages
Note: Add fme_rejection_code and fme_rejection_message to the output schema
AttributeExposer_4
    ATTR_LIST = fme_rejection_code,fme_rejection_message,attribute1,attribute2,attribute3,attribute4,attribute5,attribute6,attribute7,attribute8,attribute9,attribute10
    -> Tester
Note: Test whether the output feature has a rejection code
Tester
    BOOL_OP = OR
    TEST_CLAUSE = TEST fme_rejection_code ATTRIBUTE_IS_MISSING ""
    TEST_MODE = TEST
    PASSED -> AttributeRemover_3
    FAILED -> <REJECTED> (output)
Note: Remove fme_rejection_code and fme_rejection_message from the schema
AttributeRemover_3
    REMOVE_ATTRS = attribute10,attribute9,$(attribute4),fme_rejection_code,attribute6,$(attribute5),fme_rejection_message,attribute1,attribute4,id,attribute8,$(attribute9),$(attribute10),$(attribute1),$(attribute8),attribute5,attribute3,$(attribute7),$(attribute3),$(attribute2),attribute7,$(attribute6),attribute2
    -> Output (output)
Note: Add fme_rejection_code and fme_rejection_message to the output schema
AttributeExposer_3
    ATTR_LIST = fme_rejection_code,fme_rejection_message,attribute1,attribute2,attribute3,attribute4,attribute5,attribute6,attribute7,attribute8,attribute9,attribute10
    -> Tester_2
Note: Test whether the output feature has a rejection code
Tester_2
    BOOL_OP = OR
    TEST_CLAUSE = TEST fme_rejection_code ATTRIBUTE_IS_MISSING ""
    TEST_MODE = TEST
    PASSED -> AttributeRemover_2
    FAILED -> <REJECTED> (output)
Note: Remove fme_rejection_code and fme_rejection_message from the schema
AttributeRemover_2
    REMOVE_ATTRS = attribute10,attribute9,$(attribute4),fme_rejection_code,attribute6,$(attribute5),fme_rejection_message,attribute1,attribute4,id,attribute8,$(attribute9),$(attribute10),$(attribute1),$(attribute8),attribute5,attribute3,$(attribute7),$(attribute3),$(attribute2),attribute7,$(attribute6),attribute2
    -> Cluster_Means (output)
Note: Add fme_rejection_code and fme_rejection_message to the output schema
AttributeExposer_5
    ATTR_LIST = fme_rejection_code,fme_rejection_message,attribute1,attribute2,attribute3,attribute4,attribute5,attribute6,attribute7,attribute8,attribute9,attribute10
    -> Tester_3
Note: Test whether the output feature has a rejection code
Tester_3
    BOOL_OP = OR
    TEST_CLAUSE = TEST fme_rejection_code ATTRIBUTE_IS_MISSING ""
    TEST_MODE = TEST
    PASSED -> AttributeRemover_4
    FAILED -> <REJECTED> (output)
Note: Remove fme_rejection_code and fme_rejection_message from the schema
AttributeRemover_4
    REMOVE_ATTRS = attribute10,attribute9,$(attribute4),fme_rejection_code,attribute6,$(attribute5),fme_rejection_message,attribute1,attribute4,id,attribute8,$(attribute9),$(attribute10),$(attribute1),$(attribute8),attribute5,attribute3,$(attribute7),$(attribute3),$(attribute2),attribute7,$(attribute6),attribute2
    -> Complete (output)
Note: Add fme_rejection_code and fme_rejection_message to the output schema
AttributeExposer_6
    ATTR_LIST = fme_rejection_code,fme_rejection_message,attribute1,attribute2,attribute3,attribute4,attribute5,attribute6,attribute7,attribute8,attribute9,attribute10
    -> <REJECTED> (output)

Bookmark: Calculate cluster means
Note: Calculate cluster means
StatisticsCalculator
    COMPUTE_HISTOGRAM = NO
    GROUP_BY = cluster
    MEAN_ATTR = _mean
    PREPEND_ATTR_NAME_CHOICE = For multiple results only
    STATS_ATTRS = attribute6 attribute5 attribute7 attribute3 attribute10 attribute4 attribute8 attribute9 attribute1 attribute2
    SUMMARY -> AttributeRenamer
Note: Rename attributes to original names
AttributeRenamer
    ATTR_TABLE:
      RENAME_SET_DEFAULT attribute1._mean > $(attribute1)._mean
      RENAME_SET_DEFAULT attribute2._mean > $(attribute2)._mean
      RENAME_SET_DEFAULT attribute3._mean > $(attribute3)._mean
      RENAME_SET_DEFAULT attribute4._mean > $(attribute4)._mean
      RENAME_SET_DEFAULT attribute5._mean > $(attribute5)._mean
      RENAME_SET_DEFAULT attribute6._mean > $(attribute6)._mean
      RENAME_SET_DEFAULT attribute7._mean > $(attribute7)._mean
      RENAME_SET_DEFAULT attribute8._mean > $(attribute8)._mean
      RENAME_SET_DEFAULT attribute9._mean > $(attribute9)._mean
      RENAME_SET_DEFAULT attribute10._mean > $(attribute10)._mean
    -> AttributeExposer_3
    -> FeatureJoiner_2 [RIGHT]
Note: Create complete data stream with original data and cluster means
FeatureJoiner_2
    ATTR_CONFLICT_RES = Use Left
    GEOMETRY_HANDLING = Use Left
    JOIN_KEYS = cluster cluster AUTO
    JOIN_MODE = Left
    JOINED -> AttributeExposer_5
    <REJECTED> -> <REJECTED> (output)

Bookmark: Add rejection code and rejection message
AttributeCreator_10
    ATTR_TABLE:
      SET_TO fme_rejection_code = INVALID_ATTRIBUTE_VALUE
      SET_TO fme_rejection_message = Unable to convert attribute $(attribute10) to the required input type of real64
    -> Junction
AttributeCreator_9
    ATTR_TABLE:
      SET_TO fme_rejection_code = INVALID_ATTRIBUTE_VALUE
      SET_TO fme_rejection_message = Unable to convert attribute $(attribute9) to the required input type of real64
    -> Junction
AttributeCreator_8
    ATTR_TABLE:
      SET_TO fme_rejection_code = INVALID_ATTRIBUTE_VALUE
      SET_TO fme_rejection_message = Unable to convert attribute $(attribute8) to the required input type of real64
    -> Junction
AttributeCreator_7
    ATTR_TABLE:
      SET_TO fme_rejection_code = INVALID_ATTRIBUTE_VALUE
      SET_TO fme_rejection_message = Unable to convert attribute $(attribute7) to the required input type of real64
AttributeCreator_6
    ATTR_TABLE:
      SET_TO fme_rejection_code = INVALID_ATTRIBUTE_VALUE
      SET_TO fme_rejection_message = Unable to convert attribute $(attribute6) to the required input type of real64
    -> Junction
AttributeCreator_5
    ATTR_TABLE:
      SET_TO fme_rejection_code = INVALID_ATTRIBUTE_VALUE
      SET_TO fme_rejection_message = Unable to convert attribute $(attribute5) to the required input type of real64
    -> Junction
AttributeCreator_4
    ATTR_TABLE:
      SET_TO fme_rejection_code = INVALID_ATTRIBUTE_VALUE
      SET_TO fme_rejection_message = Unable to convert attribute $(attribute4) to the required input type of real64
AttributeCreator_3
    ATTR_TABLE:
      SET_TO fme_rejection_code = INVALID_ATTRIBUTE_VALUE
      SET_TO fme_rejection_message = Unable to convert attribute $(attribute3) to the required input type of real64
    -> Junction
AttributeCreator_2
    ATTR_TABLE:
      SET_TO fme_rejection_code = INVALID_ATTRIBUTE_VALUE
      SET_TO fme_rejection_message = Unable to convert attribute $(attribute2) to the required input type of real64
    -> Junction
AttributeCreator_1
    ATTR_TABLE:
      SET_TO fme_rejection_code = INVALID_ATTRIBUTE_VALUE
      SET_TO fme_rejection_message = Unable to convert attribute $(attribute1) to the required input type of real64
    -> Junction
AttributeCreator_algorithm
    ATTR_TABLE:
      SET_TO fme_rejection_code = INVALID_ATTRIBUTE_VALUE
      SET_TO fme_rejection_message = Please enter one of "Hartigan-Wong", "Lloyd", "Forgy", or "MacQueen" for the kmeans algorithm.
    -> Junction
AttributeCreator_nstart
    ATTR_TABLE:
      SET_TO fme_rejection_code = INVALID_ATTRIBUTE_VALUE
      SET_TO fme_rejection_message = Please enter an integer for the number of random sets.
    -> Junction
AttributeCreator_iter.max
    ATTR_TABLE:
      SET_TO fme_rejection_code = INVALID_ATTRIBUTE_VALUE
      SET_TO fme_rejection_message = Please enter an integer for the maximum number of iterations.
    -> Junction
AttributeCreator_centers
    ATTR_TABLE:
      SET_TO fme_rejection_code = INVALID_ATTRIBUTE_VALUE
      SET_TO fme_rejection_message = Please enter an integer for the number of clusters.
    -> Junction
